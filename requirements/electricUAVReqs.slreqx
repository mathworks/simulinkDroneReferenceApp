# electricUAVReqs

## #25: Flight Controller (Functional)
Aircraft shall provide an off-the-shelof flight computer to autonomously control the aircraft from launch to recovery

### #38: Sensors (Container)

#### SENS_1: Temperature Compensation (Functional)
All sensor drivers shall account for temperature-induced bias in their readings

#### SENS_2: Filtering (Functional)
Al sensor drivers shall filter for noise reading at a bandwidth of 40 Hz.

### #41: Guidance (Container)

#### GDNC_1: Waypoint Traversal (Functional)
Aricraft shall follow a given set of waypoints by the operator via a ground control station in triads of latitude, longitude, and height.

##### WP_GDNC_1: Enabling WP Guidance - Flying to Initial Point (Functional)
When WPEnable is True, aircraft shall start on a guidance path from Home Location to WP 1 (TO_IP State)

##### WP_GDNC_2: Reaching Initial Point in Wayoint Path (Functional)
When aircraft is in a guidance path from Home Location to WP1 (TO_IP State), it shall remain on that path until distance to switch point is less than or equal to zero

###### WP_GDNC_2_1: Initial Point Computation (Functional)
Guidance shall establish an initial Point (IP) for the aircraft to fly to upon Waypoint Guidance enabling. This point will be computed as follows:
IP = WP_f - L_2*IP_star*T
Where,
IP => Initial Point
WP_f => Waypoint From
L_2 => L2 Lookahead Distance
IP_star => IP Scale Factor
T => T Vector fromt the Frenet Frame
This IP Will only be visited on the first go through of the waypoint mission

###### WP_GDNC_2_2: WPT Computation when in TO_IP State (Functional)
When aircraft is in a guidance path from Home Location to WP1 (TO_IP State), WPT's X and Y coordinates shall be the computed IP_location

##### WP_GDNC_3: Transition to Next Waypoint (Functional)
When distance to switch point is less than or equal to zero Current WP shall be incremented (REACHED_IP.SWITCH_WP)

###### WP_GDNC_3_1: Wrapping Around the Waypoint Sequence (Functional)
When switching waypoint, ToWP shall wrap around to WP 2 if ToWP + 1 is greater than MaxWP

##### WP_GDNC_4: Distance To Waypoint Computation (Functional)
Guidance shall compute the distance to the destination waypoint (to WP) as a projection of its current position into the FromWP - ToWP path.

##### WP_GDNC_5: Turn Lead Time on Waypoint Transition (Functional)
Guidance shall account for an user-configurable lead time transition expressed in seconds before reaching the waypoint. I.e. aircraft will transition to next waypoint X secodns before reaching its current destination.

##### WP_GDNC_6: Frenet Frame Computation (Functional)
Guidance shall compute the T and N components of the Frenet Frame as follows:
T = | WP_t - WP_f |
N = | [-T_y, T_x, 0]|
Where
WP_t => To Waypoint
WP_F => From Waypoint
T_x => X Component of T vector
T_y => Y Component of T vector

##### WP_GDNC_8: WP Guidance Mode (Functional)
When autopilot is put in WP Guidance Mode, Guidance mode shall be 2

##### WP_GDNC_9: To Waypoint Calculation (Functional)
When aircraft is in a guidance path along the waypoint mission (REACHED_IP) the WPT coordinates shall be those of ToWP

##### WP_GDNC_10: Selecting a Minimum Path Distance for WP Guidance (Functional)
Guidance shall choose, for the minimum Down Path distance, the smallest between the Maximum Intercept Angle Distance and the Along Track Distance

###### WP_GDNC_10_1: Selecting L2 Down Path Distance (Functional)
Guidance shall choose, for the L2 Down Path Distance, the largest between the minimum down path and the minimum intersect path

###### WP_GDNC_10_2: Avoiding Flying Beyond To Waypoint (Functional)
To prevent the computed aimpoint to go beyond WPT, the L2 Down Path distance shall not be no smaller than 0

#### GDNC_2: Waypoint Orbiting (Functional)
Aricraft shall orbit at around a given waypoint in a triad of Latitude, Longitude and Height, by the operator via a ground control station

#### GDNC_3: Automatic Return to Land (Functional)
Guidance locic shall go into return-to-base mode when such command is received from the Ground Control Station

#### GDNC_5: Maximum Roll Angle Command (Functional)
The commanded roll angle, produced by the guidance logic, shall not exceed 25 degrees in either direction.

#### GDNC_6: Airspeed Command Limits (Functional)
The commanded airspeed, produced by the guidance logic, shall be, at all times between 14 and 35 m/s

#### GDNC_7: Altitude Command Limits (Functional)
The commanded altitude, produced by the guidance logic, shall never be less than the altitude of the ground station plus 20 meters.

#### GDNC_8: Transition from Manual to Autonomous Flight (Functional)
Upon transition from manual mode to autonomous. WPEnable shall be True for one complete sample time.

### #42: Control (Container)

#### CTRL_1: Airspeed Controller (Functional)
Aircraft shall be able to reach and hold a commanded airspeed from an outside component.

##### UHOLD_1: Throttle Command Limits (Functional)
Speed Controller shall provide means to limit the computed throttle command from 0% to 95%

##### UHOLD_2: Airspeed Controller Anti-Windup Protection (Functional)
All integrators part of the airspeed controller shall implement logic to avoid the numerical phenomenon knows as integrator-windup.

##### UHOLD_3: Trim Position Contribution to Airspeed Controller (Functional)
Airspeed Controller shall account for captured throttle trim conditions when producing throttle commands.

#### CTRL_2: Altitude Controller (Functional)
Aircraft shall be able to reach and hold a commanded altitude from an outside component.

##### HHOLD_1: Rate-Limit Altitude Command (Functional)
Altitude Controller shall limit the rate at which the altitude command is received.

##### HHOLD_2: Altitude Rate Limiter's Initial Conditions (Functional)
The Altitude Command Rate Limiter shall account for initial conditions different than zero and appropriately reset upon changing these.

##### HHOLD_4: Elevator Command Saturation (Functional)
Altitude Controller shall provide means to saturate the computed elevator command to 23 degrees in either direction

##### HHOLD_5: Altitude Controller Anti-Windup Protection (Functional)
All integrators part of the altitude controller shall implement logic to avoid the numerical phenomenon knows as integrator-windup.

##### HHOLD_6: Trim Position Contribution to Altitude Controller (Functional)
Altitude Controller shall account for captured elevator trim conditions when producing elevator commands.

##### HHOLD_3: Pitch Command Saturation (Functional)
Altitude Controller shall provide means to sature the pitch command produced in the Height Error controller to 35 degrees in either direction.

#### CTRL_3: Roll Angle Controller (Functional)
Aircraft shall be able to reach and hold a commanded roll from an outside component.

##### BAHOLD_1: Aileron Command Saturation (Functional)
Roll Angle Controller shall provide means to saturate the computed aileron command to 30 degrees in either direction

##### BAHOLD_2: Trim Position Contribution to Altitude Controller (Functional)
Roll Angle Controller shall account for captured aileron trim conditions when producing aileron commands.

##### BAHOLD_5: Roll Angle Controller Anti-Windup Protection (Functional)
All integrators part of the roll angle controller shall implement logic to avoid the numerical phenomenon knows as integrator-windup.

#### CTRL_5: Trim Conditions Capture (Functional)
Upon transition from manual to autonomous flight, the Flight Controller shall capture the current control surface position and consider these as trim position of these.

#### CTRL_4: Yaw Damper (Functional)
Flight controller shall implement a yaw damper that eliminates lateral accelerations during coordinated turns.

##### YD_1: Rudder Command Saturation (Functional)
Yaw Damper shall provide means to saturate the computed rudder command to 10 degrees in either direction

##### YD_2: Trim Position Contribution to Yaw Damper (Functional)
Yaw Damper shall account for captured rudder trim conditions when producing rudder commands.

##### YD_3: Roll Angle Controller Anti-Windup Protection (Functional)
All integrators part of the yaw damper shall implement logic to avoid the numerical phenomenon knows as integrator-windup.

##### YD_4: Lateral Acceleration Filtering (Functional)
Lateral Acceleration (a_y) readings shall be filtered for noise at a bandwidth of 10 Hz before passed to the Yaw Damper.
