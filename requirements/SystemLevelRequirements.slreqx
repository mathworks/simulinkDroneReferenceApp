# SystemLevelRequirements

## #1: Aircraft (Container)

### #2: Airworthiness (Container)

#### #3: Range (Informational)
The aircraft shall be controllable for all distances within visual line-of-sight

#### #4: Main Power (Functional)
Aircraft shall provide battery power to all onboard flight critical systems for the complete duration of the flight

#### #5: Payload Power (Functional)
Aircraft shall provide battery power for payload and its data link independent of Main Power for the complete duration of the flight

#### #6: Flight Data Recorder (Functional)
Aircraft shall provide the means to record all flight data from every component on board for the duration of the flight

#### #7: Flight Controller (Functional)
Aircraft shall provide an off-the-shelof flight computer to autonomously control the aircraft from launch to recovery

##### #30: Enclosure (Functional)
Fight computer shall be contained in an enclosure for its protection and easy connectivity to the necessary devices

#### #31: Endurance (Informational)
The aircraft shall be able to sustain uninterrupted flights for up to one hour

#### #32: Propulsion (Functional)
The aircraft's shall employ an off-the-shelf electric BLDC motor approriate to the MTOW

### #33: Communications (Container)

#### #34: Flight Control Link (Functional)
Aircraft shall provide a dedicated and permanent communications link with its ground station for command and control for all the range of operations.

#### #35: Payload Data Link (Functional)
Aircraft shall provide a dedicated and permanent payload data link for all the range of operations

### #36: Payload Capabilities (Container)

#### #37: Carrying Capacity (Functional)
Aircraft shall be able to carry up to 250 grams of payload

#### #38: Payload Bay Capacirty (Functional)
Aircraft shall provide a payload bay with at least 10,000 mm^3

#### #39: Default Payload (Functional)
Aircraft shall provide a pre-installed payload in the form a a gimbal-stabilized action camera providing Full-Motion video in high-definition video .

### #40: Construction (Container)

#### #41: Modularity (Functional)
Aircraft shall be constrocuted in modular components for easy spare part procurement and replacement

#### #42: Assembly/Disassembly Time (Functional)
Aircraft shall be able to be assembled and dissambled by a two person team within 10 minutes.

### #43: Transportation (Container)

#### #44: Transportation Case Weight (Functional)
Aircraft shall fit in a transportation case whose weight does not exceed 10 Kg.
